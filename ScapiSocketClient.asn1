ScapiSocket

DEFINITIONS EXPLICIT TAGS ::=
BEGIN

    IMPORTS
        ScapiRequest,
        ScapiResponse,
        ScapiNotification
    FROM Scapi;

    ScapiSocketRequest ::= SEQUENCE {
        req CHOICE {
            registration [0] ScapiSocketRegistrationRequest,
            notification [1] ScapiSocketNotificationRequest,
            interaction [2] ScapiRequest
        },
        ...
    }

    ScapiSocketResponse ::= SEQUENCE {
        rsp CHOICE {
            registration [0] ScapiSocketRegistrationAnswer,
            notification [1] ScapiNotification,
            interaction [2] ScapiResponse
        },
        ...
    }

    ScapiSocketRegistrationRequest ::= SEQUENCE {
        ...
    }

    ScapiSocketRegistrationAnswer ::= SEQUENCE {
        ...
    }

    ScapiSocketNotificationRequest ::= SEQUENCE {
        ...
    }

END
