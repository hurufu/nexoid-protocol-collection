Nexui

DEFINITIONS AUTOMATIC TAGS ::= BEGIN

    IMPORTS
        ScapiResponse,
        ScapiCardholderMesage
    FROM Scapi;

    UiRequest ::= SEQUENCE {
        source SourceIdentification,
        payload SEQUENCE OF SEQUENCE {
            api ApiType,
            line SEQUENCE OF UTF8String,
            cardholderMessage SEQUENCE OF ScapiCardholderMesage OPTIONAL
        },
        ...
        -- UiRequest should also contain original exchange id to be able to track each message from the source
        -- Also it may contain additional data to visualise for example enabled readers or for debugging
    }

    UiResponse ::= ScapiResponse

    ApiType ::= ENUMERATED {
        output,
        entry,
        ssn,
        interface,
        printer,
        pin
    }

    SourceIdentification ::= SEQUENCE {
        type RegisteredSourceType OPTIONAL,
        ...
    }

    RegisteredSourceType ::= ENUMERATED {
        scap,
        pap,
        hap,
        tmap
    }

 END
